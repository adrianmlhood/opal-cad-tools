(defun mark (s / fp)
  (setq fp (open "C:/Users/adria/CAD/Automations/LayerKit/lkdims/_result.txt" "a"))
  (write-line s fp)
  (close fp))
(defun C:RUNTEST ( / e ss res pre post)
  (setvar "CMDECHO" 0)
  (mark "m1-start")
  (load "C:/Users/adria/CAD/Automations/LayerKit/lkdims/lkdims-1.0.lsp")
  (mark "m2-loaded")
  (command "._DIMLINEAR" "0,0" "10,0" "0,3")
  (mark "m3-dim1")
  (command "._DIMLINEAR" "0,0" "0,10" "-3,0")
  (mark "m4-dim2")
  (setq ss (ssget "_X" '((0 . "DIMENSION"))))
  (mark (strcat "m5-count=" (if ss (itoa (sslength ss)) "0")))
  (setq pre "")
  (if ss (foreach e (vl-remove-if 'listp (mapcar 'cadr (ssnamex ss)))
    (setq pre (strcat pre " " (vl-princ-to-string (lk:dim-tfill e))))))
  (mark (strcat "m6-pre=" pre))
  (setq res (lk:dims-run T T))
  (mark (strcat "m7-return=" (vl-princ-to-string res)))
  (setq post "")
  (if ss (foreach e (vl-remove-if 'listp (mapcar 'cadr (ssnamex ss)))
    (setq post (strcat post " " (vl-princ-to-string (lk:dim-tfill e))))))
  (mark (strcat "m8-post=" post))
  (mark "DONE")
  (princ))
