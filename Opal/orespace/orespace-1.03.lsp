;; ============================================================
;; orespace-1.03  --  O-RESPACE / O-SPACE  : array row re-spacing
;; Companion: O-ROWS  (measure-only: report rows + inter-row spacing, no move)
;; Ocotillo Labs LLC  --  O-Suite (Opal Energy, Solesca exports)
;;
;; CHANGES vs 1.02
;;   - Optional MODULE-LAYER measurement filter. Inter-row spacing was being
;;     contaminated by racking/strings whose hardware sits inside the module gap
;;     (rail splices, clips, ballast) -- so the reading dropped below the true
;;     module-to-module gap and varied with how many such bits were in each row.
;;     Now you can pick ONE module; spacing edges are measured from that layer
;;     only. Grouping (and, in O-RESPACE, the MOVE) still use the FULL selection,
;;     so everything stays aligned and everything still moves -- only the spacing
;;     readout is restricted to the module layer. Enter = measure all selected
;;     (1.02 behavior). A row with no module-layer entity falls back to all.
;;   - The "ents" column now shows the count actually MEASURED (modules per row
;;     when a module layer is set) -- uniform count = clean detection.
;;
;; PURPOSE
;;   Re-space an array's rows when the racking system changes (e.g. Unirac
;;   GridFlex 10 -> RM10 EVO). Keeps the anchor row fixed and pushes every
;;   subsequent row away from it by a cumulative inter-row spacing change.
;;
;; WHY A DIRECTION VECTOR (not "south = -Y")
;;   Solesca exports modules ROTATED to the site/racking orientation. So the
;;   spacing direction is picked: click the row that STAYS FIXED, then click
;;   toward the rows that move. Every selected entity is projected onto that
;;   direction; entities at the same projected position = one row. Rows sort from
;;   the anchor (smallest projection) outward. Row k (0 = anchor) shifts by
;;       0                         for the anchor row
;;       dlt1 + (k-1)*dlt2         for k >= 1
;;   along the direction. The shift differences ARE the inter-row spacing changes:
;;   gap(1) grows by dlt1, every later gap by dlt2. RM10 EVO from a 13" GridFlex
;;   baseline: dlt1 = 0.5 (north bay 13->13.5), dlt2 = 1.5 (13->14.5). Negative
;;   deltas shrink gaps.
;;
;; DESIGN NOTES (per O-Suite CLAUDE.md)
;;   - Grouping center: midpoint of each entity's projected extent (full selection).
;;   - Row edges: true projected geometry via dual-path vertex read (LWPOLYLINE
;;     group 10 + heavyweight POLYLINE VERTEX walk, OCS->WCS by entity name);
;;     non-poly entities fall back to projected WCS bbox corners. All wrapped in
;;     vl-catch-all-apply -- an unmeasurable entity is skipped, never fatal.
;;   - You SELECT the entities (ssget); details / SLDs / title blocks untouched.
;;   - Always prints the plan and requires explicit Yes (default No) before moving.
;;   - vla-move per entity; locked-layer failures caught + reported as a fail count.
;; ============================================================

(vl-load-com)

;; --- normalize a 2D vector; (1 0) if degenerate ---
(defun _ors-norm (v / len)
  (setq len (sqrt (+ (* (car v) (car v)) (* (cadr v) (cadr v)))))
  (if (> len 1e-9) (list (/ (car v) len) (/ (cadr v) len)) (list 1.0 0.0)))

;; --- unit WCS direction from UCS points a -> b ---
(defun _ors-dir (a b / aw bw)
  (setq aw (trans a 1 0) bw (trans b 1 0))
  (_ors-norm (list (- (car bw) (car aw)) (- (cadr bw) (cadr aw)))))

;; --- scalar projection of point p onto unit dir d ---
(defun _ors-proj (p d) (+ (* (car p) (car d)) (* (cadr p) (cadr d))))

;; --- right-pad string s to width w ---
(defun _ors-pad (s w / r) (setq r s) (while (< (strlen r) w) (setq r (strcat r " "))) r)

;; --- is this VERTEX a real polyline corner? (skip spline-frame / mesh vertices) ---
(defun _ors-geom-vtx-p (vd / fl)
  (setq fl (cdr (assoc 70 vd)))
  (or (null fl)
      (and (= 0 (logand fl 16)) (= 0 (logand fl 64)) (= 0 (logand fl 128)))))

;; --- WCS corner points of an LWPOLYLINE or heavyweight POLYLINE; nil otherwise.
;;     Numeric-validated: only points whose x AND y are numbers reach (trans). ---
(defun _ors-poly-pts (ent / ed et pts pr v vd raw)
  (setq ed (entget ent) et (cdr (assoc 0 ed)) pts '())
  (cond
    ((= et "LWPOLYLINE")
     (foreach pr ed
       (if (and (= (car pr) 10) (numberp (cadr pr)) (numberp (caddr pr)))
         (setq pts (cons (trans (list (cadr pr) (caddr pr) 0.0) ent 0) pts)))))
    ((= et "POLYLINE")
     (setq v (entnext ent))
     (while (and v (= (cdr (assoc 0 (setq vd (entget v)))) "VERTEX"))
       (setq raw (cdr (assoc 10 vd)))
       (if (and (_ors-geom-vtx-p vd) raw (numberp (car raw)) (numberp (cadr raw)))
         (setq pts (cons (trans (list (car raw) (cadr raw) 0.0) ent 0) pts)))
       (setq v (entnext v)))))
  pts)

;; --- WCS bbox (minpt maxpt) of ANY entity via native VLA; nil on failure ---
(defun _ors-bbox (ent / res mn mx o)
  (setq res (vl-catch-all-apply
              (function (lambda ()
                (setq o (vlax-ename->vla-object ent))
                (vla-getboundingbox o 'mn 'mx)
                (list (vlax-safearray->list mn) (vlax-safearray->list mx))))))
  (if (vl-catch-all-error-p res) nil res))

;; --- WCS points that bound an entity along any direction: true polyline corners
;;     if available, else the four WCS bbox corners. nil if nothing measurable. ---
(defun _ors-points (ent / pts bb)
  (setq pts (vl-catch-all-apply (function (lambda () (_ors-poly-pts ent)))))
  (if (vl-catch-all-error-p pts) (setq pts nil))
  (if (and pts (>= (length pts) 2))
    pts
    (if (setq bb (_ors-bbox ent))
      (list (list (car  (car bb)) (cadr (car  bb)))
            (list (car  (cadr bb)) (cadr (car  bb)))
            (list (car  (cadr bb)) (cadr (cadr bb)))
            (list (car  (car bb)) (cadr (cadr bb)))))))

;; --- projected extent of an entity onto dir d: (minproj maxproj center) or nil ---
(defun _ors-extent (ent d / pts p tp mn mx)
  (if (setq pts (_ors-points ent))
    (progn
      (foreach p pts
        (setq tp (_ors-proj p d))
        (if (or (null mn) (< tp mn)) (setq mn tp))
        (if (or (null mx) (> tp mx)) (setq mx tp)))
      (if (and mn mx) (list mn mx (/ (+ mn mx) 2.0))))))

;; --- insertion sort of records (ent center minp maxp layer) ascending by center ---
(defun _ors-sort (lst / sorted xp tmp r inserted)
  (setq sorted '())
  (foreach xp lst
    (setq inserted nil tmp '())
    (foreach r sorted
      (if (and (not inserted) (< (cadr xp) (cadr r)))
        (progn (setq tmp (append tmp (list xp r))) (setq inserted T))
        (setq tmp (append tmp (list r)))))
    (setq sorted (if inserted tmp (append tmp (list xp)))))
  sorted)

;; --- group ascending recs into rows by center gap > tol.
;;     Returns groups (ascending); each group = list of recs (ent center minp maxp layer). ---
(defun _ors-group (recs tol / groups cur prevp r p)
  (setq groups '() cur '() prevp nil)
  (foreach r recs
    (setq p (cadr r))
    (if (and prevp (> (- p prevp) tol))
      (progn (setq groups (cons (reverse cur) groups)) (setq cur '())))
    (setq cur (cons r cur))
    (setq prevp p))
  (if cur (setq groups (cons (reverse cur) groups)))
  (reverse groups))

;; --- (measuredCount nearEdge farEdge) of a row group along the direction.
;;     If mlayer is set, edges come from that layer only; a row with none of that
;;     layer falls back to all its entities. ---
(defun _ors-rowext (g mlayer / r mn mx cnt)
  (setq cnt 0)
  (foreach r g
    (if (or (null mlayer) (= (nth 4 r) mlayer))
      (progn
        (if (or (null mn) (< (caddr r)  mn)) (setq mn (caddr r)))
        (if (or (null mx) (> (cadddr r) mx)) (setq mx (cadddr r)))
        (setq cnt (1+ cnt)))))
  (if (and mlayer (= cnt 0))
    (progn
      (foreach r g
        (if (or (null mn) (< (caddr r)  mn)) (setq mn (caddr r)))
        (if (or (null mx) (> (cadddr r) mx)) (setq mx (cadddr r))))
      (setq cnt (length g))))
  (list cnt mn mx))

;; --- move one entity by (dx dy); T on success, nil on failure (e.g. locked) ---
(defun _ors-move (ent dx dy / res o)
  (setq res (vl-catch-all-apply
              (function (lambda ()
                (setq o (vlax-ename->vla-object ent))
                (vla-move o (vlax-3d-point 0.0 0.0 0.0) (vlax-3d-point dx dy 0.0))))))
  (if (vl-catch-all-error-p res) nil T))

;; --- prompt for spacing direction (two-point pick); unit WCS vector or nil ---
(defun _ors-get-dir ( / old-os p1 p2)
  (setq old-os (getvar "OSMODE"))
  (setvar "OSMODE" 0)
  (setq p1 (getpoint "\nPick a point AT the row that stays fixed: "))
  (if p1 (setq p2 (getpoint p1 "\nPick a point toward the rows that move: ")))
  (setvar "OSMODE" old-os)
  (if (and p1 p2) (_ors-dir p1 p2)))

;; --- prompt for an optional module layer (pick one module); nil = measure all ---
(defun _ors-get-mlayer ( / e ly)
  (setq e (entsel "\nPick ONE module to measure spacing from its layer (or Enter = all selected): "))
  (if e
    (progn
      (setq ly (cdr (assoc 8 (entget (car e)))))
      (prompt (strcat "\n  measuring inter-row spacing from layer: " ly))
      ly)))

;; --- build sorted, grouped rows from a selection set + direction ---
(defun _ors-rows (ss d tol / recs i n en ext nbad)
  (setq recs '() nbad 0 i 0 n (sslength ss))
  (while (< i n)
    (setq en (ssname ss i) ext (_ors-extent en d))
    (if ext
      (setq recs (cons (list en (caddr ext) (car ext) (cadr ext)
                             (cdr (assoc 8 (entget en)))) recs))
      (setq nbad (1+ nbad)))
    (setq i (1+ i)))
  (if (> nbad 0)
    (prompt (strcat "\n  (" (itoa nbad) " entit" (if (= nbad 1) "y" "ies")
                    " skipped -- no measurable geometry.)")))
  (_ors-group (_ors-sort recs) tol))

;; ============================================================
;; O-RESPACE -- the re-spacing command
;; ============================================================
(defun C:O-RESPACE ( / old-err old-os old-ce ss d mlayer tol dlt1 dlt2 groups
                       k g ext2 rmin rmax prevmax sp m dx dy ans nmoved nfail r)
  (vl-load-com)
  (setq old-err *error*)
  (defun *error* (msg)
    (if old-os (setvar "OSMODE" old-os))
    (if old-ce (setvar "CMDECHO" old-ce))
    (setq *error* old-err)
    (if (and msg (/= msg "Function cancelled") (/= msg "quit / exit abort"))
      (prompt (strcat "\nO-RESPACE error: " msg)))
    (princ))
  (setq old-os (getvar "OSMODE") old-ce (getvar "CMDECHO"))

  (prompt "\nO-RESPACE: select array entities to re-space (modules, racking, strings):")
  (setq ss (ssget))
  (cond
    ((null ss) (prompt "\nNothing selected."))
    ((null (setq d (_ors-get-dir)))
     (prompt "\nNo spacing direction given -- aborted."))
    (T
     (setq mlayer (_ors-get-mlayer))
     (setq dlt1 (getreal "\nFirst inter-row spacing change (north bay) <0.5>: "))
     (if (null dlt1) (setq dlt1 0.5))
     (setq dlt2 (getreal "\nEach subsequent inter-row spacing change <1.5>: "))
     (if (null dlt2) (setq dlt2 1.5))
     (setq tol (getreal "\nRow grouping tolerance <3.0>: "))
     (if (null tol) (setq tol 3.0))

     (setq groups (_ors-rows ss d tol))
     (if (< (length groups) 2)
       (prompt "\nFewer than 2 rows detected -- nothing to move. Try a larger tolerance or recheck the direction (O-ROWS).")
       (progn
         ;; --- plan ---
         (prompt (strcat "\n\nO-RESPACE plan -- " (itoa (length groups))
                         " rows along the spacing direction (row 1 = anchor, fixed):"))
         (prompt "\n  row   ents   spacing(prev)   shift")
         (setq k 0 prevmax nil)
         (foreach g groups
           (setq ext2 (_ors-rowext g mlayer)
                 rmin (cadr ext2)
                 rmax (caddr ext2)
                 sp   (if prevmax (- rmin prevmax) nil)
                 m    (if (= k 0) 0.0 (+ dlt1 (* (- k 1) dlt2))))
           (prompt (strcat "\n  "
                           (_ors-pad (itoa (1+ k)) 6)
                           (_ors-pad (itoa (car ext2)) 7)
                           (_ors-pad (if sp (rtos sp 2 2) "--") 16)
                           (rtos m 2 3) "\""))
           (setq prevmax rmax k (1+ k)))
         ;; --- confirm ---
         (initget "Yes No")
         (setq ans (getkword "\n\nApply this re-spacing? [Yes/No] <No>: "))
         (if (= ans "Yes")
           (progn
             (setq k 0 nmoved 0 nfail 0)
             (foreach g groups
               (setq m (if (= k 0) 0.0 (+ dlt1 (* (- k 1) dlt2))))
               (if (> (abs m) 1e-9)
                 (progn
                   (setq dx (* m (car d)) dy (* m (cadr d)))
                   (foreach r g
                     (if (_ors-move (car r) dx dy)
                       (setq nmoved (1+ nmoved))
                       (setq nfail (1+ nfail))))))
               (setq k (1+ k)))
             (prompt (strcat "\nO-RESPACE: done -- " (itoa nmoved) " entities moved across "
                             (itoa (1- (length groups))) " shifted rows."))
             (if (> nfail 0)
               (prompt (strcat "\n  WARNING: " (itoa nfail)
                               " entities could not move (locked layer?). Unlock and re-run."))))
           (prompt "\nO-RESPACE: cancelled -- nothing moved."))))))
  (setvar "OSMODE" old-os)
  (setvar "CMDECHO" old-ce)
  (setq *error* old-err)
  (princ))

;; ============================================================
;; O-ROWS -- measure-only: report detected rows + inter-row spacing, no move
;; ============================================================
(defun C:O-ROWS ( / ss d mlayer tol groups k g ext2 rmin rmax prevmax sp gaps mn mx sm)
  (vl-load-com)
  (prompt "\nO-ROWS: select array entities to analyze (no changes made):")
  (setq ss (ssget))
  (cond
    ((null ss) (prompt "\nNothing selected."))
    ((null (setq d (_ors-get-dir))) (prompt "\nNo spacing direction given -- aborted."))
    (T
     (setq mlayer (_ors-get-mlayer))
     (setq tol (getreal "\nRow grouping tolerance <3.0>: "))
     (if (null tol) (setq tol 3.0))
     (setq groups (_ors-rows ss d tol))
     (prompt (strcat "\nO-ROWS: " (itoa (length groups)) " rows detected."))
     (setq k 0 prevmax nil gaps '())
     (foreach g groups
       (setq ext2 (_ors-rowext g mlayer)
             rmin (cadr ext2)
             rmax (caddr ext2)
             sp   (if prevmax (- rmin prevmax) nil))
       (prompt (strcat "\n  row " (_ors-pad (itoa (1+ k)) 5)
                       " ents " (_ors-pad (itoa (car ext2)) 6)
                       " inter-row spacing(prev) " (if sp (rtos sp 2 3) "--")))
       (if sp (setq gaps (cons sp gaps)))
       (setq prevmax rmax k (1+ k)))
     (if gaps
       (progn
         (setq mn (car gaps) mx (car gaps) sm 0.0)
         (foreach sp gaps
           (if (< sp mn) (setq mn sp))
           (if (> sp mx) (setq mx sp))
           (setq sm (+ sm sp)))
         (prompt (strcat "\n  inter-row spacing (edge-to-edge):  min " (rtos mn 2 3)
                         "   max " (rtos mx 2 3)
                         "   avg " (rtos (/ sm (length gaps)) 2 3)))
         (prompt "\n  (uniform spacing = clean detection; if it still varies, pick a module so racking/strings are excluded)")))))
  (princ))

;; --- aliases (O-Suite: dashed + undashed) ---
(defun C:ORESPACE () (C:O-RESPACE))
(defun C:O-SPACE  () (C:O-RESPACE))
(defun C:OSPACE   () (C:O-RESPACE))
(defun C:OROWS    () (C:O-ROWS))

(prompt "\nO-RESPACE v1.03 loaded. Commands: O-RESPACE / O-SPACE  (re-space)  |  O-ROWS  (check only)")
(princ)
