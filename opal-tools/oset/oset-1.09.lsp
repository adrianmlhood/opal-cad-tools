;; oset-1.09.lsp -- O-Suite Project Parameter Setup
;; Commands: O-SET (alias: OSET)
;; Auto-calibrate: scan modules on the configured layer, derive module W/H and
;; the column/row gaps. No click.
;; v1.09 -- pitch is now the MOST COMMON spacing (mode of the sampled pitches),
;;          not the pitch closest to module size. With the v1.08 footprint
;;          filter cleaning out non-module clutter, the dominant pitch cluster
;;          is the real spacing; min-|gap| wrongly favoured the smaller of two
;;          real gaps (e.g. picked 13.5 when 14.5 is the common one).
;; v1.08 -- module size = MODE (dominant footprint); keep only polylines whose
;;          W*H matches that footprint, ignore other elements on the layer.
;; v1.07 -- pitch distribution diagnostic.
;; v1.06 -- pitch selection minimises |gap|. v1.05 -- per-module sampling.
;; v1.04 -- defensive: skip any entity it cannot read as a 4-corner module.
;; ============================================================

(if (not *oset-mod-w*) (setq *oset-mod-w* nil))
(if (not *oset-mod-h*) (setq *oset-mod-h* nil))
(if (not *oset-gap-x*) (setq *oset-gap-x* nil))
(if (not *oset-gap-y*) (setq *oset-gap-y* nil))

(defun _oset-lmin (lst / v r) (setq r (car lst)) (foreach v (cdr lst) (if (< v r) (setq r v))) r)
(defun _oset-lmax (lst / v r) (setq r (car lst)) (foreach v (cdr lst) (if (> v r) (setq r v))) r)
(defun _oset-sum  (lst / v r) (setq r 0.0) (foreach v lst (setq r (+ r v))) r)
(defun _oset-sub  (a b) (list (- (car a) (car b)) (- (cadr a) (cadr b))))
(defun _oset-len  (a)   (sqrt (+ (* (car a) (car a)) (* (cadr a) (cadr a)))))
(defun _oset-dot  (a b) (+ (* (car a) (car b)) (* (cadr a) (cadr b))))
(defun _oset-unit (a / l) (setq l (_oset-len a)) (if (> l 1e-9) (list (/ (car a) l) (/ (cadr a) l)) (list 1.0 0.0)))

(defun _oset-modlayer ()
  (if (and (boundp (quote *ocfg-layer-modules*)) *ocfg-layer-modules*)
    *ocfg-layer-modules* nil))

;; corners as WCS points (LWPOLYLINE group 10, or heavyweight POLYLINE VERTEX walk)
(defun _oset-poly-pts (ent / ed typ pts pr sub sd p)
  (setq ed (entget ent) typ (cdr (assoc 0 ed)) pts nil)
  (cond
    ((= typ "LWPOLYLINE")
     (foreach pr ed
       (if (= (car pr) 10)
         (setq pts (cons (trans (list (cadr pr) (caddr pr) 0.0) ent 0) pts)))))
    ((= typ "POLYLINE")
     (setq sub (entnext ent))
     (while (and sub (setq sd (entget sub)) (= (cdr (assoc 0 sd)) "VERTEX"))
       (if (setq p (cdr (assoc 10 sd)))
         (setq pts (cons (trans p ent 0) pts)))
       (setq sub (entnext sub)))))
  (reverse pts))

;; T if p looks like a numeric 2D/3D point
(defun _oset-pt-ok (p) (and (listp p) (numberp (car p)) (numberp (cadr p))))

;; module record: (ent center la lb u v minx miny maxx maxy), or nil if unusable
(defun _oset-rec (ent / pts p0 p1 p2 p3 xs ys)
  (setq pts (_oset-poly-pts ent))
  (if (< (length pts) 4)
    nil
    (progn
      (setq p0 (nth 0 pts) p1 (nth 1 pts) p2 (nth 2 pts) p3 (nth 3 pts))
      (if (not (and (_oset-pt-ok p0) (_oset-pt-ok p1) (_oset-pt-ok p2) (_oset-pt-ok p3)))
        nil
        (progn
          (setq xs (list (car p0) (car p1) (car p2) (car p3))
                ys (list (cadr p0) (cadr p1) (cadr p2) (cadr p3)))
          (list ent
                (list (/ (_oset-sum xs) 4.0) (/ (_oset-sum ys) 4.0))
                (_oset-len  (_oset-sub p1 p0))
                (_oset-len  (_oset-sub p3 p0))
                (_oset-unit (_oset-sub p1 p0))
                (_oset-unit (_oset-sub p3 p0))
                (_oset-lmin xs) (_oset-lmin ys) (_oset-lmax xs) (_oset-lmax ys)))))))

;; build records from a selection set, skipping any entity that errors
(defun _oset-recs-from (ss / i ent r lst)
  (setq i 0 lst nil)
  (while (< i (sslength ss))
    (setq ent (ssname ss i)
          r (vl-catch-all-apply (function _oset-rec) (list ent)))
    (if (and (not (vl-catch-all-error-p r)) r) (setq lst (cons r lst)))
    (setq i (1+ i)))
  lst)

;; ---- histogram / mode helpers ----------------------------------------------
(defun _oset-round (v bin) (* bin (fix (+ 0.5 (/ v bin)))))

;; -> list of (binCentre . count)
(defun _oset-hist (pitches bin / v k cell tbl)
  (setq tbl nil)
  (foreach v pitches
    (setq k (_oset-round v bin) cell (assoc k tbl))
    (if cell
      (setq tbl (subst (cons k (1+ (cdr cell))) cell tbl))
      (setq tbl (cons (cons k 1) tbl))))
  tbl)

;; modal value: precise mean of the values forming the most-populated cluster
;; (windowed +/- bin around the winning bin so a split boundary doesn't bias it)
(defun _oset-mode (vals bin / tbl best bestc cell sum cnt v)
  (setq tbl (_oset-hist vals bin) best nil bestc -1)
  (foreach cell tbl (if (> (cdr cell) bestc) (setq best (car cell) bestc (cdr cell))))
  (setq sum 0.0 cnt 0)
  (foreach v vals
    (if (<= (abs (- v best)) bin) (setq sum (+ sum v) cnt (1+ cnt))))
  (if (> cnt 0) (/ sum cnt) best))

;; the value shared by the MOST samples: pick the value whose +/- tol cluster is
;; largest, then return that cluster's precise mean. tol stays below the spacing
;; between distinct clusters so two real pitches (e.g. 58 vs 59) aren't merged.
(defun _oset-mode-cluster (vals tol / p q cnt best bestc sum n)
  (setq best nil bestc -1)
  (foreach p vals
    (setq cnt 0)
    (foreach q vals (if (<= (abs (- q p)) tol) (setq cnt (1+ cnt))))
    (if (> cnt bestc) (setq best p bestc cnt)))
  (if best
    (progn
      (setq sum 0.0 n 0)
      (foreach q vals (if (<= (abs (- q best)) tol) (setq sum (+ sum q) n (1+ n))))
      (/ sum n))
    nil))

;; top n (binCentre . count) pairs by count, descending
(defun _oset-topn (tbl nmax / out best bestc c)
  (setq out nil)
  (while (and tbl (< (length out) nmax))
    (setq best nil bestc -1)
    (foreach c tbl (if (> (cdr c) bestc) (setq best c bestc (cdr c))))
    (setq out (append out (list best)) tbl (vl-remove best tbl)))
  out)

(defun _oset-hist-str (pitches bin nmax / s c)
  (setq s "")
  (foreach c (_oset-topn (_oset-hist pitches bin) nmax)
    (setq s (strcat s (rtos (car c) 2 1) "x" (itoa (cdr c)) "  ")))
  (if (= s "") "(none)" s))
;; -----------------------------------------------------------------------------

;; nearest in-band neighbour pitch from ONE module along each module axis.
(defun _oset-pitch1 (pick recs / c u v la lb r rc dvec du dv pitu pitv)
  (setq c (nth 1 pick) la (nth 2 pick) lb (nth 3 pick) u (nth 4 pick) v (nth 5 pick))
  (foreach r recs
    (if (not (eq (car r) (car pick)))
      (progn
        (setq rc (nth 1 r)
              dvec (list (- (car rc) (car c)) (- (cadr rc) (cadr c)))
              du (_oset-dot dvec u) dv (_oset-dot dvec v))
        (if (and (< (abs dv) (* 0.5 lb)) (> (abs du) (* 0.5 la)))
          (if (or (not pitu) (< (abs du) pitu)) (setq pitu (abs du))))
        (if (and (< (abs du) (* 0.5 la)) (> (abs dv) (* 0.5 lb)))
          (if (or (not pitv) (< (abs dv) pitv)) (setq pitv (abs dv)))))))
  (list pitu pitv))

;; keep only records whose footprint matches the dominant module (modw x modh)
(defun _oset-match-mods (recs modw modh / tw th out r)
  (setq tw (max 1.0 (* 0.05 modw)) th (max 1.0 (* 0.05 modh)) out nil)
  (foreach r recs
    (if (and (<= (abs (- (nth 2 r) modw)) tw) (<= (abs (- (nth 3 r) modh)) th))
      (setq out (cons r out))))
  out)

(defun C:O-SET ( / ml ss n recs las lbs modw modh mods nmod pus pvs r p pu pv e0 pts0)
  (vl-load-com)
  (setq ml (_oset-modlayer))
  (prompt (strcat "\nO-SET -- module layer: " (if ml ml "<none set>")))
  (setq ss (ssget "X" (if ml (list (quote (0 . "*POLYLINE")) (cons 8 ml)) (list (quote (0 . "*POLYLINE")))))
        n  (if ss (sslength ss) 0))
  (prompt (strcat "\nScanned " (itoa n) " polyline(s) on the layer."))
  (if (= n 0)
    (prompt "\nNo polylines found. Check the module layer name in oconfig (O-CONFIG).")
    (progn
      (setq recs (_oset-recs-from ss))
      (prompt (strcat "\n4-corner polylines: " (itoa (length recs)) "."))
      (if (null recs)
        (progn
          (setq e0 (ssname ss 0) pts0 (_oset-poly-pts e0))
          (prompt (strcat "\nFirst entity: type=" (cdr (assoc 0 (entget e0)))
                          ", corners read=" (itoa (length pts0))))
          (prompt "\nModules are not 4-corner polylines as expected -- send me this readout."))
        (progn
          ;; dominant module footprint = MODE of W and H over all 4-corner polys
          (setq las nil lbs nil)
          (foreach r recs (setq las (cons (nth 2 r) las) lbs (cons (nth 3 r) lbs)))
          (setq modw (_oset-mode las 2.0) modh (_oset-mode lbs 2.0))
          ;; drop non-module elements: keep only matching footprints
          (setq mods (_oset-match-mods recs modw modh) nmod (length mods))
          (prompt (strcat "\nMatching module footprint (" (rtos modw 2 2) " x " (rtos modh 2 2)
                          "): " (itoa nmod) "  (ignored " (itoa (- (length recs) nmod))
                          " non-module object(s))."))
          ;; pitch sampled from the matched modules ONLY
          (setq pus nil pvs nil)
          (foreach r mods
            (setq p (_oset-pitch1 r mods))
            (if (car p)  (setq pus (cons (car p)  pus)))
            (if (cadr p) (setq pvs (cons (cadr p) pvs))))
          ;; spacing = the MOST COMMON pitch (tol 0.5 keeps 58 vs 59 distinct)
          (setq pu (if pus (_oset-mode-cluster pus 0.5) nil)
                pv (if pvs (_oset-mode-cluster pvs 0.5) nil))
          (setq *oset-mod-w* modw *oset-mod-h* modh
                *oset-gap-x* (if pu (- pu modw) nil)
                *oset-gap-y* (if pv (- pv modh) nil))
          (prompt "\n--- O-SET parameters (auto) ---")
          (prompt (strcat "\n  Module W: " (rtos *oset-mod-w* 2 4)
                          "   Module H: " (rtos *oset-mod-h* 2 4)))
          (prompt (strcat "\n  Pitch X:  " (if pu (rtos pu 2 4) "(none)")
                          "   Gap X: " (if *oset-gap-x* (rtos *oset-gap-x* 2 4) "(no neighbour)")))
          (prompt (strcat "\n  Pitch Y:  " (if pv (rtos pv 2 4) "(none)")
                          "   Gap Y: " (if *oset-gap-y* (rtos *oset-gap-y* 2 4) "(no neighbour)")))
          (prompt (strcat "\n  Sampled " (itoa (length pus)) " X-neighbours, "
                          (itoa (length pvs)) " Y-neighbours."))
          (prompt (strcat "\n  X-pitch clusters: " (_oset-hist-str pus 1.0 6)))
          (prompt (strcat "\n  Y-pitch clusters: " (_oset-hist-str pvs 1.0 6)))))))
  (princ))

(defun C:OSET () (C:O-SET))

(prompt "\nO-SET v1.09 loaded. Type O-SET or OSET to auto-calibrate (no clicking).")
(princ)
